package BusinessGoals {
    // Бизнес-цели Заказчика (начальника службы эксплуатации БЛА)

    requirement <BG> 'Бизнес-цели UAVLog' {
        requirement <BG1> 'БЦ-1 Единый учёт парка' {
            doc /* Вести учёт всех БЛА, АКБ и полезной нагрузки
             * в одной базе вместо бумажных формуляров и таблиц Excel. */
        }
        requirement <BG2> 'БЦ-2 Достоверный налёт' {
            doc /* Автоматически считать налёт, число полётов
             * и циклы АКБ по записям о полётах. */
        }
        requirement <BG3> 'БЦ-3 ТО без просрочек' {
            doc /* Заблаговременно предупреждать о приближении ТО
             * и исключить полёты с просроченным ТО. */
        }
        requirement <BG4> 'БЦ-4 Контроль допуска' {
            doc /* Не допускать к полёту неисправный борт
             * и оператора с истёкшим допуском. */
        }
        requirement <BG5> 'БЦ-5 Быстрая отчётность' {
            doc /* Формировать формуляр борта и сводный отчёт
             * за период не дольше 1 минуты. */
        }
    }
}
