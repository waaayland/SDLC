package UAVLogUseCases {
    // Варианты использования ПО UAVLog
    private import UAVLogContext::*;

    use case def <UC1> 'ВИ-1 Вести реестр БЛА и комплектующих' {
        subject 'ПО UAVLog' : 'Программное средство';
        actor 'Начальник службы' : 'Пользователь';
    }
    use case def <UC2> 'ВИ-2 Вести реестр операторов и допусков' {
        subject 'ПО UAVLog' : 'Программное средство';
        actor 'Начальник службы' : 'Пользователь';
    }
    use case def <UC3> 'ВИ-3 Зарегистрировать полёт' {
        subject 'ПО UAVLog' : 'Программное средство';
        actor 'Оператор БЛА' : 'Пользователь';
    }
    use case def <UC4> 'ВИ-4 Внести выполненное ТО' {
        subject 'ПО UAVLog' : 'Программное средство';
        actor 'Техник' : 'Пользователь';
    }
    use case def <UC5> 'ВИ-5 Зарегистрировать неисправность' {
        subject 'ПО UAVLog' : 'Программное средство';
        actor 'Техник' : 'Пользователь';
        actor 'Оператор БЛА' : 'Пользователь';
    }
    use case def <UC6> 'ВИ-6 Сформировать отчёт' {
        subject 'ПО UAVLog' : 'Программное средство';
        actor 'Начальник службы' : 'Пользователь';
        actor 'Руководитель' : 'Пользователь';
    }
}
